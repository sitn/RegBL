FME workspace integrateEcapData_ctrlEGID.fmw

Parameters:
- GDENR = 6408   # gdenr
- DestDataset_XLSXW = C:\temp\RegBL\output\6408.xlsx   # Destination Microsoft Excel File
- SourceDataset_XLSXR_8 = C:\Users\rufenerm\Desktop\RegBL\Extension_complements_batiments\brut\6434.xlsx   # Source Microsoft Excel File(s)
- SourceDataset_POSTGIS = sitn_intranet_mapfish   # Connection
- SourceDataset_XLSXR_9 = $(FME_MF_DIR)static\Tableau_correspondance_MO_REGBL_OFS_v3.xlsx   # Source Microsoft Excel File(s)
- SourceDataset_XLSXR_5 = $(FME_MF_DIR)static\Export_SITN_EGID.xlsx   # Source Microsoft Excel File(s)
- SourceDataset_XLSXR = $(FME_MF_DIR)static\Tableau_correspondance_ECAP_REGBL_OFS_v2.xlsx   # Source Microsoft Excel File(s)
- SourceDataset_POSTGIS_6 = sitn_intranet_mapfish   # Connection
- SourceDataset_POSTGIS_7 = sitn_intranet_mapfish   # Connection

Readers:
- XLSXR_4: XLSXR from $(SourceDataset_XLSXR_8) in EPSG:2056
- POSTGIS_1: POSTGIS from $(SourceDataset_POSTGIS) in EPSG:2056
- XLSXR_1: XLSXR from $(SourceDataset_XLSXR_9)
- XLSXR_2: XLSXR from $(SourceDataset_XLSXR)
- XLSXR_3: XLSXR from $(SourceDataset_XLSXR_5) in EPSG:2056
- POSTGIS_2: POSTGIS from $(SourceDataset_POSTGIS_6)
- POSTGIS_3: POSTGIS from $(SourceDataset_POSTGIS_7) in EPSG:2056

Writers:
- XLSXW_1: XLSXW to $(DestDataset_XLSXW) in EPSG:2056

mo22_batiments (reader POSTGIS_1)
    attributes: idobj char(40),PrimaryKey, numcom int8, numele varchar(5), desnat varchar(30), mutmut varchar(20), desspe varchar(100), surfba float8, batddp varchar(20), datedt date, typcou varchar(15), nufeco varchar(5), ideddp varchar(20), desba1 varchar(30), desba2 varchar(30), desba3 varchar(30), base varchar(30), fksurf varchar(40), valide date, egid int4
    -> StringConcatenator
StringConcatenator
    ACTION = Create New Attribute
    PARM_LINE = fme_basicstring:14%1%14%1%14:@Value(desba1) @Value(desba2) @Value(desba3)
    VAL_ATTR = desbat
    -> AttributeRemover_3
AttributeRemover_3
    REMOVE_ATTRS = base,batddp,datedt,desspe,fksurf,ideddp,mutmut,nufeco,surfba,typcou,valide,desba1,desba2,desba3,numcom,numele
    -> StringReplacer_4
StringReplacer_4
    CASE = NO
    FIND_TEXT = " "
    NO_MATCH = _FME_NO_OP_
    REGEXP = NO
    SRC_ATTRS = desnat
    -> StringCaseChanger
StringCaseChanger
    ATTRCHOICE = Selected Attributes
    ATTRLIST = desnat
    CHANGE_TYPE = lowercase
    -> AttributeTrimmer_2
AttributeTrimmer_2
    SRC_ATTRS = desnat
    TRIM_CHARS = " "
    TRIM_TO_NONE = Yes
    TRIM_TYPE = Both
    -> FeatureMerger_4 [REQUESTOR]
Feuil1 (reader XLSXR_1)
    attributes: Désignation char(32), Spécification char(230), GKAT char(15), GKLAS char(15), Commentaires David Vieille, OFS char(87), F string
    -> AttributeManager_3
AttributeManager_3
    ATTR_TABLE:
      REMOVE Spécification
      RENAME_SET_VALUE GKAT
      RENAME_SET_VALUE GKLAS
      REMOVE Commentaires David Vieille, OFS
      REMOVE F
    -> StringReplacer_2
StringReplacer_2
    CASE = NO
    FIND_TEXT = " "
    NO_MATCH = _FME_NO_OP_
    REGEXP = NO
    SRC_ATTRS = Désignation
    -> StringReplacer_6
StringReplacer_6
    CASE = NO
    FIND_TEXT = ’
    NO_MATCH = _FME_NO_OP_
    REGEXP = NO
    REPLACE_TEXT = '
    SRC_ATTRS = Désignation
    -> StringCaseChanger_2
StringCaseChanger_2
    ATTRCHOICE = Selected Attributes
    ATTRLIST = Désignation
    CHANGE_TYPE = lowercase
    -> AttributeTrimmer
AttributeTrimmer
    SRC_ATTRS = Désignation
    TRIM_CHARS = " "
    TRIM_TO_NONE = Yes
    TRIM_TYPE = Both
    -> FeatureMerger_4 [SUPPLIER]
FeatureMerger_4
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(desnat) @Value(Désignation) STRING
    MERGE_TYPE = Attributes Only
    PROCESS_DUPS = YES
    REJECT_NULL_MISSING_KEYS = No
    SUPPLIERS_FIRST = No
    MERGED -> BulkAttributeRenamer_2
BulkAttributeRenamer_2
    ATTRCHOICE = All Attributes
    MODE_CHOICE = RENAME
    PATTERN_ACTION_DISP = ADDPREFIX
    REPLACE_STR = CS_
    -> SpatialFilter_2 [Candidate]
6434 (reader XLSXR_4)
    attributes: RefCode char(11), Typ char(20), GDEKT char(3), GDENR number(5,0), GDENAME char(22), EGID number(10,0), EDID number(2,0), STRNAME char(23), DEINR char(6), PLZ4 number(5,0), PLZNAME char(22), GKAT number(5,0), GKLAS number(5,0), Control1 char(3), GBAUJ number(5,0), GBAUP char(12), Control2 char(3), DOFFADR char(4), alternativ_STRNAME string, alternativ_DEINR string, Delete char(4), Link_mapgeo char(5), GEBNR number(9,1), GBEZ char(29), Objektname BB string, Gebaeudename GEB char(1), GPARZ char(7), EGRID char(15), GAREA number(5,0), GKODE x_coordinate,
      GKODN y_coordinate, Control3 char(3), DKODE number(12,3), DKODN number(11,3), ESTRID number(8,0), PLZZ number(2,0), Ref_3 char(4), Distanz number(7,1), Adresse char(53), Dupl. number(2,0), FlagKeinDEINR number(2,0), FlagDistanz number(2,0), FlagSpeChar number(2,0), ESTRSX number(2,0), FlagHadOnlySTRNAME string, Grundbuchkreis string, NBIDENT string
    -> AttributeCreator
AttributeCreator
    ATTR_TABLE = SET_TO xlsx_row_id_bk = @Value(xlsx_row_id)
    -> Tester_7
Tester_7
    BOOL_OP = OR
    TEST_CLAUSE:
      CASE_INSENSITIVE_TEST @Value(Typ) LIKE MO slt sans adresse
      CASE_INSENSITIVE_TEST @Value(Typ) LIKE MO slt avec adresse
    TEST_MODE = TEST
    PASSED -> FeatureMerger_2 [REQUESTOR]
Note: Données travaillées par la commune (guichet carto)
eg02_egid_cne_edition (reader POSTGIS_2)
    attributes: idobj varchar(40),PrimaryKey, refcode varchar(11), typ varchar(20), gdekt varchar(3), gdenr int4, gdename varchar(100), strname varchar(100), deinr varchar(20), plz4 int4, plzname varchar(100), gkat int4,BTree, gklas int4,BTree, gkode float8, gkodn float8, controle1 numeric(20,10), propadres varchar(15), controle2 int2, numcom int2, couleur varchar(100), numbat varchar(100), covoie int4, date_maj_num date, date_maj_cat_clas date, num_ok bool, catclas_ok bool
    -> AttributeManager_2
AttributeManager_2
    ATTR_TABLE:
      REMOVE idobj
      REMOVE typ
      REMOVE gdekt
      REMOVE gdenr
      REMOVE gdename
      REMOVE plz4
      REMOVE plzname
      REMOVE gkode
      REMOVE gkodn
      REMOVE controle1
      REMOVE propadres
      REMOVE controle2
      REMOVE numcom
      REMOVE couleur
      REMOVE numbat
      REMOVE covoie
      REMOVE date_maj_num
      REMOVE date_maj_cat_clas
    -> BulkAttributeRenamer_3
BulkAttributeRenamer_3
    ATTRCHOICE = All Attributes
    MODE_CHOICE = RENAME
    PATTERN_ACTION_DISP = ADDPREFIX
    REPLACE_STR = COMMUNE_
    -> StringReplacer
StringReplacer
    CASE = NO
    FIND_TEXT = _
    NO_MATCH = _FME_NO_OP_
    REGEXP = NO
    REPLACE_TEXT = " "
    SRC_ATTRS = COMMUNE_strname
    -> FeatureMerger_2 [SUPPLIER]
FeatureMerger_2
    ATTR_ACCUM_MODE = Merge Supplier
    ATTR_CONFLICT_RES = Use Requestor
    IGNORE_NULLS = No
    JOIN_KEYS = @Value(RefCode) @Value(COMMUNE_refcode) AUTO
    MERGE_TYPE = Attributes Only
    PROCESS_DUPS = NO
    REJECT_NULL_MISSING_KEYS = No
    SUPPLIERS_FIRST = No
    MERGED -> SpatialFilter_2 [Filter]
    UNMERGED_REQUESTOR -> SpatialFilter_2 [Filter]
Note: Lien RegBL avec CS + OD
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = WITHIN
    USE_BOUNDING_BOX = No
    PASSED -> SpatialFilter_3 [Candidate]
mo7_obj_divers_surface (reader POSTGIS_3)
    attributes: idobj varchar(40),PrimaryKey, fkobj varchar(40), base varchar(30), genre int2, genre_txt varchar(40), typline int2, nomline varchar(30)
    -> AttributeRemover_7
AttributeRemover_7
    REMOVE_ATTRS = base,fkobj,genre,genre_txt,idobj,nomline,typline
    -> AttributeCreator_2
AttributeCreator_2
    ATTR_TABLE:
      SET_TO remarque = Bâtiment souterrain
      SET_TO GKAT = 1080
    -> BulkAttributeRenamer_4
BulkAttributeRenamer_4
    ATTRCHOICE = All Attributes
    MODE_CHOICE = RENAME
    PATTERN_ACTION_DISP = ADDPREFIX
    REPLACE_STR = OD_
    -> SpatialFilter_3 [Filter]
Note: Ctrl OD --> GKAT 1080
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = EQUALS
    USE_BOUNDING_BOX = No
    PASSED -> SpatialFilter [Candidate]
    FAILED -> SpatialFilter [Candidate]
Note: Data from ECAP
DATA (reader XLSXR_3)
    attributes: No Obj number(5,0), Statut Obj char(4), Code Commune number(3,0), Nom Commune char(26), Code Cadastre number(3,0), Nom Cadastre char(26), No Parcelle char(22), Adresse Obj char(58), No Egid char(24), Ann Constr number(5,0), Libelle Obj char(74), Code Aeai number(4,0), Affectation char(34), Coord X x_coordinate, Coord Y y_coordinate
    -> Tester
Note: Contrôle que l'objet a des coordonnées
Tester
    BOOL_OP = AND
    TEST_CLAUSE:
      TEST Coord X ATTRIBUTE_HAS_A_VALUE ""
      TEST Coord Y ATTRIBUTE_HAS_A_VALUE ""
    TEST_MODE = TEST
    PASSED -> AttributeRemover
AttributeRemover
    REMOVE_ATTRS = Adresse Obj,Affectation,Code Cadastre,Code Commune,Libelle Obj,No Parcelle,Nom Cadastre,Nom Commune,Statut Obj
    -> FeatureMerger [REQUESTOR]
Note: Codes AEAI ECAP
Feuil1 (reader XLSXR_2)
    attributes: CODE_ECAP char(71), DESCRIPTION char(279), LET char(4), GKAT char(17), GKLAS char(11), F string
    -> AttributeManager_5
AttributeManager_5
    ATTR_TABLE:
      REMOVE DESCRIPTION
      REMOVE LET
      REMOVE F
    -> FeatureMerger [SUPPLIER]
FeatureMerger
    ATTR_ACCUM_MODE = Merge Supplier
    ATTR_CONFLICT_RES = Use Requestor
    IGNORE_NULLS = No
    JOIN_KEYS = @Value(Code Aeai) @Value(CODE_ECAP) AUTO
    MERGE_TYPE = Attributes Only
    PROCESS_DUPS = NO
    REJECT_NULL_MISSING_KEYS = No
    SUPPLIERS_FIRST = No
    MERGED -> AttributeRemover_2
AttributeRemover_2
    REMOVE_ATTRS = Code Aeai,CODE_ECAP
    -> BulkAttributeRenamer
BulkAttributeRenamer
    ATTRCHOICE = All Attributes
    MODE_CHOICE = RENAME
    PATTERN_ACTION_DISP = ADDPREFIX
    REPLACE_STR = ECAP_
    -> SpatialFilter [Filter]
    -> NeighborFinder_2 [CANDIDATE]
Note: Enregistre les GKLASS et GKAT sur les empreintes de la MO
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = WITHIN TOUCHES
    USE_BOUNDING_BOX = No
    PASSED -> Tester_8
    FAILED -> NeighborFinder_2 [BASE]
Note: Si bâtiment souterrain
Tester_15
    BOOL_OP = OR
    TEST_CLAUSE = TEST @Value(OD_GKAT) = 1080
    TEST_MODE = TEST
    PASSED -> AttributeManager_18
    FAILED -> AttributeManager_7
AttributeManager_18
    ATTR_TABLE:
      SET_TO GKAT = @Value(OD_GKAT)
      SET_TO GBEZ = Bâtiment souterrain
    -> Tester_2
AttributeManager_7
    ATTR_TABLE = SET_TO CS_GKAT = @ReplaceString(@Value(CS_GKAT),", 1080","",caseSensitive=TRUE)
    -> Tester_9
Note: Si gkat et gklas sont enregistrés par la commune
Tester_9
    BOOL_OP = OR
    TEST_CLAUSE = CASE_INSENSITIVE_TEST COMMUNE_catclas_ok ATTRIBUTE_HAS_A_VALUE ""
    TEST_MODE = CASE_INSENSITIVE_TEST
    PASSED -> AttributeManager_12
    FAILED -> Tester_10
AttributeManager_12
    ATTR_TABLE:
      SET_TO GKAT = @Value(COMMUNE_gkat)
      SET_TO GKLAS = @Value(COMMUNE_gklas)
    -> Tester_14
Tester_2
    BOOL_OP = OR
    TEST_CLAUSE = CASE_INSENSITIVE_TEST @Value(GKAT) NOT_= 1040, 1060
    TEST_MODE = CASE_INSENSITIVE_TEST
    PASSED -> Tester_11
    FAILED -> Tester_4
AttributeManager_17_Output: Inspector
Note: Création nouvel attribut "remarque sgrf" (dernière colonne du fichier excel)
AttributeCreator_3
    ATTR_TABLE = SET_TO Remarque SGRF
    -> Tester_16
AttributeRemover_8
    REMOVE_ATTRS = Adresse,COMMUNE_catclas_ok,COMMUNE_deinr,COMMUNE_gkat,COMMUNE_gklas,COMMUNE_num_ok,COMMUNE_refcode,COMMUNE_strname,CS_Désignation,CS_GKAT,CS_GKLAS,CS_desnat,CS_idobj,Control1,Control2,Control3,DEINR,DKODE,DKODN,DOFFADR,Distanz,Dupl.,ECAP_Ann Constr,ECAP_Coord X,ECAP_Coord Y,ECAP_GKAT,ECAP_GKLAS,ECAP_No Egid,ECAP_No Obj,EDID,EGID,EGRID,ESTRID,ESTRSX,FlagDistanz,FlagHadOnlySTRNAME,FlagKeinDEINR,FlagSpeChar,GAREA,GBAUP,GBEZ,GDEKT,GDENAME,GDENR,GKODE,GKODN,GPARZ,Gebaeudename GEB,Grundbuchkreis,NBIDENT,OD_GKAT,OD_remarque,Objektname BB,PLZ4,PLZNAME,PLZZ,RefCode,Ref_3,STRNAME,Typ,_predicate,xlsx_row_id_bk,Link_mapgeo,CS_egid,GEBNR
    -> 6434 (writer XLSXW_1)
6434 (writer XLSXW_1)
    attributes: RefCode string(11), Typ string(20), GDEKT string(3), GDENR number(5), GDENAME string(22), EGID number(10), EDID number(2), STRNAME string(23), DEINR string(6), PLZ4 number(5), PLZNAME string(22), GKAT number(5), GKLAS number(5), Control1 string(3), GBAUJ number(5), GBAUP string(12), Control2 string(3), DOFFADR string(4), alternativ_STRNAME string(20), alternativ_DEINR string(20), Delete string(4), Link_mapgeo string(5), GEBNR number(9), GBEZ string(29), Objektname BB string(20), Gebaeudename GEB string(1), GPARZ string(7), EGRID string(15), GAREA number(5), GKODE number(12),
      GKODN number(12), Control3 string(3), DKODE number(12), DKODN number(11), ESTRID number(8), PLZZ number(2), Ref_3 string(4), Distanz number(7), Adresse string(53), Dupl. number(2), FlagKeinDEINR number(2), FlagDistanz number(2), FlagSpeChar number(2), ESTRSX number(2), FlagHadOnlySTRNAME string(20), Grundbuchkreis string(20), NBIDENT string(20), ESID string(20), Remarque SGRF string(20)

Bookmark: Recherche voisinage 10m
NeighborFinder_2
    ATTR_ACCUM_MODE = Merge Candidate
    ATTR_CONFLICT_RES = Use Base
    CANDIDATES_FIRST = No
    INSERT_VERTEX = No
    K = 1
    MAX = 10
    MEASURES_FROM_CANDIDATE = Yes
    MEASURE_TYPE = Continuous
    MODE = Bases and Candidates
    TREAT_POLYGON_AS = Areas
    MATCHED -> AttributeRemover_5
    UNMATCHED_BASE -> AttributeRemover_5
AttributeRemover_5
    REMOVE_ATTRS = _angle,_candidate_angle,_candidate_label_angle,_closest_base_x,_closest_base_y,_closest_candidate_x,_closest_candidate_y,_distance,_predicate
    -> Tester_8

Bookmark: Année de construction
Tester_8
    BOOL_OP = OR
    TEST_CLAUSE = TEST GBAUJ NOT_ATTRIBUTE_HAS_A_VALUE ""
    TEST_MODE = TEST
    PASSED -> AttributeManager_11
    FAILED -> Tester_15
AttributeManager_11
    ATTR_TABLE = SET_TO GBAUJ = @Value(ECAP_Ann Constr)
    -> Tester_15

Bookmark: GKAT
Note: si gkat dans CS
Tester_10
    BOOL_OP = OR
    TEST_CLAUSE = TEST CS_GKAT ATTRIBUTE_HAS_A_VALUE ""
    TEST_MODE = TEST
    PASSED -> AttributeManager_13
    FAILED -> Tester_12
AttributeManager_13
    ATTR_TABLE = SET_TO GKAT = @Value(CS_GKAT)
    -> Tester_2
Note: si gkat dans ECAP
Tester_12
    BOOL_OP = OR
    TEST_CLAUSE = TEST CS_GKAT ATTRIBUTE_HAS_A_VALUE ""
    TEST_MODE = TEST
    PASSED -> AttributeManager_14
    FAILED -> Tester_2
AttributeManager_14
    ATTR_TABLE = SET_TO GKAT = @Value(ECAP_GKAT)
    -> Tester_2

Bookmark: Tester valeurs 1040, 1060
Tester_4
    BOOL_OP = OR
    TEST_CLAUSE = CASE_INSENSITIVE_TEST @Value(CS_desnat) CONTAINS habitation
    TEST_MODE = CASE_INSENSITIVE_TEST
    PASSED -> AttributeManager_4
    FAILED -> AttributeManager_6
AttributeManager_4
    ATTR_TABLE:
      SET_TO GKAT = 1040
      SET_TO Delete = oui
    -> Tester_11
AttributeManager_6
    ATTR_TABLE = SET_TO GKAT = 1060
    -> Tester_11

Bookmark: GKLAS
Note: si gklas dans CS
Tester_11
    BOOL_OP = OR
    TEST_CLAUSE = TEST CS_GKLAS ATTRIBUTE_HAS_A_VALUE ""
    TEST_MODE = TEST
    PASSED -> AttributeManager_15
    FAILED -> Tester_13
AttributeManager_15
    ATTR_TABLE = SET_TO GKLAS = @Value(CS_GKLAS)
    -> Tester_14
Note: si gkat dans ECAP
Tester_13
    BOOL_OP = OR
    TEST_CLAUSE = TEST ECAP_GKLAS ATTRIBUTE_HAS_A_VALUE ""
    TEST_MODE = TEST
    PASSED -> AttributeManager_16
    FAILED -> Tester_14
AttributeManager_16
    ATTR_TABLE = SET_TO GKLAS = @Value(ECAP_GKLAS)
    -> Tester_14

Bookmark: Adresses
Tester_14
    BOOL_OP = OR
    TEST_CLAUSE = CASE_INSENSITIVE_TEST @Value(COMMUNE_num_ok) LIKE f
    TEST_MODE = CASE_INSENSITIVE_TEST
    PASSED -> AttributeManager_17
    FAILED -> AttributeManager_17_Output
    FAILED -> Tester_3
AttributeManager_17
    ATTR_TABLE:
      SET_TO alternativ_STRNAME = FME_CONDITIONAL:DEFAULT_VALUE'_FME_NO_OP_'BOOL_OP;OR;COMPOSITE_TEST;1;CASE_INSENSITIVE_TEST @Value(COMMUNE_strname) NOT_LIKE @Value(STRNAME)'@Value(COMMUNE_strname)'FME_NUM_CONDITIONS2___
      SET_TO alternativ_DEINR = FME_CONDITIONAL:DEFAULT_VALUE'_FME_NO_OP_'BOOL_OP;OR;COMPOSITE_TEST;1;CASE_INSENSITIVE_TEST @Value(alternativ_DEINR) NOT_LIKE @Value(DEINR)'@Value(COMMUNE_deinr)'FME_NUM_CONDITIONS2___
    -> AttributeManager_17_Output
    -> Tester_3

Bookmark: delete gkat < 1060
Tester_3
    BOOL_OP = COMPOSITE
    COMPOSITE_TEST = ( 1 OR 2 ) AND (NOT 3 )
    TEST_CLAUSE:
      CASE_INSENSITIVE_TEST @Value(GKAT) CONTAINS ,
      TEST @Value(GKAT) >= 1060
      CASE_INSENSITIVE_TEST @Value(GKAT) LIKE 1020, 1030
    TEST_MODE = PER_TEST
    PASSED -> AttributeCreator_3
    FAILED -> AttributeManager
AttributeManager
    ATTR_TABLE:
      SET_TO GKAT = FME_NULL_VALUE
      SET_TO GKLAS = FME_NULL_VALUE
      SET_TO GBAUJ = FME_NULL_VALUE
      SET_TO alternativ_STRNAME = FME_NULL_VALUE
      SET_TO alternativ_DEINR = FME_NULL_VALUE
      SET_TO Delete = oui
    -> AttributeCreator_3

Bookmark: Afficher Designation et DesNat si bâtiment delete=true
Tester_16
    BOOL_OP = OR
    TEST_CLAUSE = CASE_INSENSITIVE_TEST @Value(Delete) LIKE oui
    TEST_MODE = TEST
    PASSED -> AttributeManager_10
    FAILED -> Tester_5
AttributeManager_10
    ATTR_TABLE = SET_TO Remarque SGRF = Désignation(s) MO: @Value(CS_Désignation)
    -> Tester_17
Tester_17
    BOOL_OP = OR
    TEST_CLAUSE = CASE_INSENSITIVE_TEST CS_desbat ATTRIBUTE_HAS_A_VALUE ""
    TEST_MODE = CASE_INSENSITIVE_TEST
    PASSED -> AttributeManager_19
    FAILED -> Tester_5
AttributeManager_19
    ATTR_TABLE = SET_TO Remarque SGRF = @Value(Remarque SGRF), @Value(CS_desbat)
    -> Tester_5

Bookmark: EGID déjà existant ?
Tester_5
    BOOL_OP = OR
    TEST_CLAUSE = TEST CS_egid ATTRIBUTE_HAS_A_VALUE ""
    TEST_MODE = TEST
    PASSED -> AttributeManager_9
    FAILED -> AttributeRemover_8
AttributeManager_9
    ATTR_TABLE:
      REMOVE GKAT
      REMOVE GKLAS
      REMOVE GBAUJ
      SET_TO Delete = oui
      SET_TO Remarque SGRF = EGID déjà existant: @Value(CS_egid)
    USER_EXPOSED_ATTRIBUTES = Remarque SGRF
    -> AttributeRemover_8

Bookmark: Pavillons < 30m2 à supprimer
Note: Pavillons: set values if area >= 30m2
Tester_6 [off]
    BOOL_OP = COMPOSITE
    COMPOSITE_TEST = 1 AND 2
    TEST_CLAUSE:
      TEST @Value(GAREA) < 30
      CASE_INSENSITIVE_TEST @LowerCase(@Value(CS_Désignation)) LIKE %pavillon%
    TEST_MODE = PER_TEST
    PASSED -> AttributeManager_8 [off]
AttributeManager_8 [off]
    ATTR_TABLE:
      SET_TO GKAT = FME_NULL_VALUE
      SET_TO GKLAS = FME_NULL_VALUE
      SET_TO Delete = oui
