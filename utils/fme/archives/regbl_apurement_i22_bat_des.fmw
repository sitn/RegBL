FME workspace regbl_apurement_i22_bat_des.fmw

Parameters:
- SourceDataset_XLSXR =   # Source Microsoft Excel File(s)
- DestDataset_XLSXW =   # Destination Microsoft Excel File
- SourceDataset_POSTGIS =   # Connection

Readers:
- XLSXR_1: XLSXR from $(SourceDataset_XLSXR)
- POSTGIS_3: POSTGIS from $(SourceDataset_POSTGIS) in EPSG:2056

Writers:
- XLSXW_1: XLSXW to $(DestDataset_XLSXW)

NE (reader XLSXR_1)
    attributes: A char(10), B char(21), C char(24), D char(32), E char(15), F char(12), G char(12)
    -> Tester_2
Tester_2
    BOOL_OP = OR
    TEST_CLAUSE = TEST @Value(E) = 22
    TEST_MODE = TEST
    PASSED -> VertexCreator
VertexCreator
    MEASURE_TYPE = Continuous
    MODE_NAME = Replace with Point
    XVAL = @Value(F)
    YVAL = @Value(G)
    -> SpatialFilter [Candidate]
mo22_batiments (reader POSTGIS_3)
    attributes: idobj char(40),PrimaryKey, numcom int8, numele varchar(5), desnat varchar(30), mutmut varchar(20), desspe varchar(100), surfba float8, batddp varchar(20), datedt date, typcou varchar(15), nufeco varchar(5), ideddp varchar(20), desba1 varchar(30), desba2 varchar(30), desba3 varchar(30), base varchar(30), fksurf varchar(40), valide date, egid int4
    -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> AttributeRemover
AttributeRemover
    REMOVE_ATTRS = C,E,G,_predicate,base,batddp,datedt,desspe,egid,fksurf,ideddp,idobj,mutmut,nufeco,numcom,numele,surfba,typcou,valide
    -> AttributeConcatenator
AttributeConcatenator
    ATTRS = desba1 desba2 desba3
    CASE = No
    DEST_ATTR = _desba
    DROP_EMPTY_PARTS = Yes
    ORDER = ValueNumericAscending
    SEP = ", "
    TRIM_OPTION = Both
    -> AttributeConcatenator_2
AttributeConcatenator_2
    ATTRS = desnat _desba
    CASE = No
    DEST_ATTR = H
    DROP_EMPTY_PARTS = Yes
    ORDER = NameDescending
    SEP = ", "
    TRIM_OPTION = Both
    -> NE (writer XLSXW_1)
NE (writer XLSXW_1)
    attributes: H auto(50)

FME custom transformer AttributeConcatenator
Concatenates selected attribute values in the order specified to the "Concatenating Order" parameter.
Resulting string consists of the original attribute values delimited by identical string specified to the "Separator String" parameter.
This transformer considers both Null value and Missing attribute as an empty string. 
See also the AttributeListPopulator.
Parameters
Attributes to Concatenate:
Select attributes which should be concatenated.
Concatenating Order:
Choose one of these as the concatenating order.
- Value Numeric Ascending: sorted by attribute value numeric ascending
- Value Numeric Descending: sorted by attribute value numeric descending
- Value Alphabetic Ascending: sorted by attribute value alphabetic ascending
- Value Alphabetic Descending: sorted by attribute value alphabetic descending
- Name Ascending (Alphabetic): sorted by attribute name alphabetic ascending
- Name Descending (Alphabetic): sorted by attribute name alphabetic descending
Note:
In "Value Numeric Ascending/Descending", the transformer considers every non-numeric value (including empty/null/missing) as 0.
But a numeric representation surrounded by white spaces will be treated as a numeric value (both leading and trailing white spaces will be ignored).
And leading 0 of a numeric representation will also be ignored when comparing it as a numeric value to other values.
Case Sensitive:
Yes: The transformer will perform case-sensitive sorting.
No (default): The transformer will perform case-insensitive sorting.
Note
The "Case Sensitive" parameter setting is basically applied to alphabetic sorting, but it will also be applied to non-numeric parts in numeric sorting, if non-numeric values exist.
Separator String:
Specify a string that will be used as the delimiter. You can set blank to this parameter not to use delimiter.
Trim Whitespaces:
By default, the transformer will remove Both leading and trailing whitespaces from every original attribute value before concatenating, but you can change the setting to either Left or Right, or None.
Destination Attribute:
Specify name of the attribute that stores the resulting string.
Drop Empty Parts:
Yes: The concatenation will be performed excluding empty parts.
No (default): The concatenation will be performed including empty parts.

Parameters:
- ATTRS =   # " " Attributes to Concatenate
- ORDER = ValueNumericAscending
- CASE = No   # Case Sensitive
- SEP = ,   # Separator String
- TRIM_OPTION = Both   # Trim Whitespaces
- DEST_ATTR = _concatenated   # TYPE:varchar(200) Destination Attribute
- DROP_EMPTY_PARTS = No   # Drop Empty Parts

Input (input)
    -> ParameterFetcher
ParameterFetcher
    ATTR_LIST = attributeconcatenator.attrs {$(ATTRS)} attributeconcatenator.sep {$(SEP)} attributeconcatenator.order {$(ORDER)} attributeconcatenator.case {$(CASE)} attributeconcatenator.trim_option {$(TRIM_OPTION)} attributeconcatenator.drop_empty {$(DROP_EMPTY_PARTS)}
    -> TclCaller
TclCaller
    SRC:
      proc concatAttrs {} {
          set attrs [FME_GetAttribute "attributeconcatenator.attrs"];
          set order [FME_GetAttribute "attributeconcatenator.order"];
          set nocase [string equal [FME_GetAttribute "attributeconcatenator.case"] {No}];
          set trimOption [FME_GetAttribute "attributeconcatenator.trim_option"];
          set trimOption [string map {Both trim Left trimleft Right trimright None ""} $trimOption];
          set keepEmpty [string equal [FME_GetAttribute "attributeconcatenator.drop_empty"] {No}];
          set sorted {};
          proc getAttr {name trimOption} {
              if {[string equal $trimOption {}]} {
                  return [FME_GetAttribute $name];
              } else {
                  return [string $trimOption [FME_GetAttribute $name]];
              };
          };
          if {[regexp {^ValueNumeric.+} $order]} {
              set num {}; set nan {};
              foreach name $attrs {
                  set v [getAttr $name $trimOption];
                  if {$keepEmpty || ![string equal $v {}]} {
                      set t [string trim $v]
                      set n [string trimleft [string range $t 0 end-1] {0}][string index $t end];
                      if {[string is double -strict $n]} {
                          lappend num [list $n $v];
                      } else {
                          lappend nan [list {0} $v];
                      };
                  };
              };
              if {$nocase} {
                  set nan [lsort -nocase -index 1 $nan];
              } else {
                  set nan [lsort -index 1 $nan];
              };
              foreach vv [lsort -real -index 0 [concat $nan $num]] {
                  lappend sorted [lindex $vv 1];
              };
          } elseif {[regexp {^ValueAlphabetic.+} $order]} {
              foreach name $attrs {
                  set v [getAttr $name $trimOption];
                  if {$keepEmpty || ![string equal $v {}]} {
                      lappend sorted $v;
                  };
              };
              if {$nocase} {
                  set sorted [lsort -nocase $sorted];
              } else {
                  set sorted [lsort $sorted];
              };
          } elseif {[regexp {^Name.+} $order]} {
              if {$nocase} {
                  set attrs [lsort -nocase $attrs];
              } else {
                  set attrs [lsort $attrs];
              };
              foreach name $attrs {
                  set v [getAttr $name $trimOption];
                  if {$keepEmpty || ![string equal $v {}]} {
                      lappend sorted $v;
                  };
              };
          } else {
              return "Debug: Invalid Concatenation Order: $order";
          };
          set delim [FME_GetAttribute "attributeconcatenator.sep"];
          if {[regexp {.+Ascending$} $order]} {
              return [join $sorted $delim];
          } elseif {[regexp {.+Descending$} $order]} {
              return [join [lreverse $sorted] $delim];
          } else {
              return "Debug: Invalid Concatenation Order: $order";
          };
      }
    TCLPROG = concatAttrs
    VAL_ATTR = attributeconcatenator.dest_attr
    -> BulkAttributeRenamer
BulkAttributeRenamer
    ATTRCHOICE = Selected Attributes
    ATTRLIST = attributeconcatenator.dest_attr
    PATTERN_ACTION_DISP = Regular Expression Replace
    REPLACE_PATTERN = .+
    REPLACE_STR = $(DEST_ATTR)
    -> BulkAttributeRemover
BulkAttributeRemover
    ATTR_EXP = ^attributeconcatenator.+
    -> Output (output)
Output (output)
