FME workspace regbl_apurement_filter_bat_proj.fmw

Parameters:
- SourceDataset_POSTGIS =   # Connection
- SourceDataset_XLSXR =   # Source Microsoft Excel File(s)
- DestDataset_XLSXW =   # Destination Microsoft Excel File

Readers:
- POSTGIS_2: POSTGIS from $(SourceDataset_POSTGIS) in EPSG:2056
- XLSXR_1: XLSXR from $(SourceDataset_XLSXR) in EPSG:2056

Writers:
- XLSXW_3: XLSXW to $(DestDataset_XLSXW) in EPSG:2056

Sheet1 (reader XLSXR_1)
    attributes: gdenr number(4,0), gdename char(21), egid number(9,0), gkat number(4,0), gklas number(4,0), gstat number(4,0), strname char(32), deinr char(8), dplz4 number(4,0), dplzname char(19), gkode number(11,3), gkodn number(11,3), out_issue_22 number(1,0), gbez char(32), gbauj number(4,0), bat_proj string, etat_mo string, Type erreur string, Aide du SGRF char(315)
    -> VertexCreator
VertexCreator
    MEASURE_TYPE_LOOKUP = CONTINUOUS
    MODE = REPLACE
    REMOVE_ATTRIBUTES = No
    XVAL = @Value(gkode)
    YVAL = @Value(gkodn)
    MEASURE_TYPE = Continuous
    MODE_NAME = Replace with Point
    -> SpatialFilter_6 [Candidate]
etat_mo (reader POSTGIS_2)
    attributes: idobj int8,PrimaryKey, no_lot int8, lettre varchar(1), type varchar(6), commune varchar(50), type2 varchar(50), validite varchar(50), adjudicataire varchar(20), chef_projet varchar(3), mpd_realise int4, mpd_prevu int4, mpd_technique varchar(50), mpd_realise_relatif int4, facture bool
    -> AttributeRemover
AttributeRemover
    REMOVE_ATTRS = adjudicataire,chef_projet,commune,facture,idobj,lettre,mpd_prevu,mpd_realise,mpd_realise_relatif,mpd_technique,no_lot,type,validite
    -> BulkAttributeRenamer
BulkAttributeRenamer
    ATTRCHOICE_ACTION = NONPROTECTEDFME
    MODE_CHOICE = RENAME
    PATTERN_ACTION_DISP = ADDPREFIX
    REPLACE_STR = etat_mo_
    ATTRCHOICE = All Attributes
    -> SpatialFilter_6 [Filter]
SpatialFilter_6
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> AttributeManager_7
    FAILED -> AttributeManager
Note: Colonne etat_mo: etat MO
AttributeManager_7
    ATTR_TABLE:
      SET_TO etat_mo (buffer) = @Value(etat_mo_type2)
      REMOVE _predicate (buffer)
    USER_EXPOSED_ATTRIBUTES = type2
    -> AttributeManager
AttributeManager
    ATTR_TABLE = SET_TO bat_proj (buffer) = 0
    -> SpatialFilter [Candidate]
AttributeRemover_7 [off]
    REMOVE_ATTRS = Aide du SGRF,bdg_link,deinr,dplz4,dplzname,gbauj,gbez,gdekt,gdename,gdenr,gebnr,gkat,gklas,gksce,gparz,gstat,issue_bdg_cat,issue_bdg_def,issue_gde,issue_issue_22,issue_plz,out_adr_com,out_adr_inc,out_bdg_cat,out_bdg_def,out_deinr,out_gde,out_gkode_n,out_issue_22,out_lpure,out_plz,strname,dkode,dkodn,edid,egid
AttributeRemover_2 [off]
    REMOVE_ATTRS = gkode,gkodn
mo23_batiments_projetes (reader POSTGIS_2)
    attributes: idobj varchar(40),Unique, numcom int2, numele varchar(10), desnat varchar(30), typcou varchar(15), nufeco varchar(6), source varchar(20), lien_plan varchar(250), lien_avis varchar(250), v_satac int2, fk_instance_id int8, affichage int2, cadastre varchar(150), commune varchar(150), idcom int2, datedt date, avis_url varchar(250), plan_url varchar(250), type_construction varchar(100), demoli int2, affich_demoli varchar(80), egid int4, date_valide date
    -> BulkAttributeRenamer_2
BulkAttributeRenamer_2
    ATTRCHOICE_ACTION = NONPROTECTEDFME
    MODE_CHOICE = RENAME
    PATTERN_ACTION_DISP = ADDPREFIX
    REPLACE_STR = mo23_batiments_projetes_
    ATTRCHOICE = All Attributes
    -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> AttributeManager_6
    FAILED -> Sheet1 (writer XLSXW_3)
Note: Colonne bat_proj: bat proj
AttributeManager_6
    ATTR_TABLE:
      REMOVE egid (number(9,0))
      SET_TO bat_proj (buffer) = 1
      REMOVE _predicate (buffer)
    -> Sheet1 (writer XLSXW_3)
Sheet1 (writer XLSXW_3)
    attributes: gdenr number(4), gdename string(21), egid number(9), gkat number(4), gklas number(4), gstat number(4), strname string(32), deinr string(8), dplz4 number(4), dplzname string(19), gkode number(11), gkodn number(11), out_issue_22 number(1), gbez string(32), gbauj number(4), bat_proj string(20), etat_mo string(20), Type erreur string(20), Aide du SGRF string(315)
